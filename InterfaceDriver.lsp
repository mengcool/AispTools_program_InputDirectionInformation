;;;InterFaceDriver

;;;OpenDCL 工程数据表
(setq INTERFACE
       '("YWt6A69dAACjb5sHBuKTIhUSaitqQK1pPSN0ts10rDTvKWnEE8mlKB3cdi/eUxM/Sl6u6BPXavQu"
	 "Vdx3XOYWPvVBaiHBSo/pnl1AfK/mhl7m7v4BSjgANur2L752fG/f4A3Yk7JDxeMflsxxRaOSCMBD"
	 "CZDjRYnikQKJMAU5CiGX+OCJroUeQwo+Zkg8TUo+bWDbf76vX36nCv47dDRfutheZP2GpfHBKZ3V"
	 "Z/E0jyvyoYTfb8ETuOwAyvrfclSOq3p/QnDfQ3pbOO2jKh1mE3Mu+tEYVrnp4fE0z/LhQX2Gl5lI"
	 "PSZlYysed9TZ4hXb6Hz2uP8xvfXCf5ZZaQrzUeAB1hErBhxViBFgiNB/qJ8XhF/Gz8k6MS/DcEy+"
	 "jN0Re9OJhlog0IBnGlSIUXrAr1KBV6jX2RUUA+HmCLhhd4LPvmF0QieX6sAaG8YIsczc20GgAQil"
	 "j+SIK4RJ9GOKF5iH+wbaCTwocaquQM93VF8Mrhk9mrPkckv2mT5lyr1YxAcl6uR0oqgKcaitegmf"
	 "xX2T4xaVHjGsxesEGcbTCRAhJ8zIPkvIHcor8aFl05a56kg+ATK/ycQT7bTIDEFkjoDKvGgUHfEW"
	 "Hem+J+T0SXXF0KQDlwYK9U/urMkRJvJzELh1xmVgu7FwkpAEcjqj2SpHjZTFS2XcqRZEP1Xgxahm"
	 "zjKv7wk7OYh0wjGeCXoQlXU/CCMD076VhCIkRTFfp1CScXXCLaoB1JGgZ4b0J+AwrjH1jYH+X3RQ"
	 "bpnhT9H5ky8mW3OKoNGKZE1cIV74tiz4TJ3tk6GrDVrBWeaWA//NM7LpU+cWwyzR0XSDQXGhFQ6u"
	 "pI7r+S+v+I8fG9KPCqC13KBP2INunztYIDPGqLptdoFQZhb0F2E1iBRtwTODIV5mEN++K3yxaWZK"
	 "iwRbfTBrg89OnMOGmMbkto6UnFROrm9Y0FigMLhvoH6UdgF0lHYJPpTzDtIXTp6vXkat3lFlcjx+"
	 "wqNc0K59JC86rhMTuaX1b0uSpPk2qKtVUWQPBiwS9uj0hJvuQ1aOdv/puRD20a6L1D3iCMrXjA/J"
	 "p7Dc4YHfVE0ycJ01zg6bH7zrWLBbYmziFr3nIiHSRo3+B2PZlsRTYiR7L0YKUIbqCFLi5HlU2axS"
	 "O2GlTTGXUyFShCtUlOknyDqKVVawKUdEkXBy+UUfN4PbpGHEcMHG3Y2PKTAJ4NdBL4MLqdqjGeER"
	 "lVTU5a/MiP8pFQWZb0VEFyjvcQke/q/nKPABNS1HQCn1f7kpvksNguGGiC+XAvjNWqUaUDgYlh4X"
	 "UCw/PGef0VpaE2mvAiw6TaUV+inWtDlVNPSGYzOLsmqLJJyLKS6dC1DWjzkcrzB9C/eGjrlcQCK6"
	 "vUqW9/lC+G+PThpfuDxdoc5+agdP76bm5uNsTw9yquYmehQysv2a8Hds3WJt7WY4ujqIbKrys9JT"
	 "NzPQT4qcHho91K5EjAU/Y4fT3vCCLDaQ71lIilawH9A4qOVnOTo46OdTtMNl564iT8oAGytjVwoo"
	 "lCMR0dYyNHifCFJyPPWoKHi3ryp4B2Ts5T8In6U5EAptvUVdKE2yO1wk/3ZHBL8SryjvvlCYsl/E"
	 "aVAC/pOseTi4tlm0O0WsOZripzgRjsTjuxkAXyJWuK5RjnKvgOl8tUcKwKyxL39WOD8ivOGKsu9A"
	 "lwZAsp/Z7TsW1X4D6Ce1u9OI4IX2jqJ7z46idK9VaeCylYnszONWRJlELQrd1oEn/5vcJqYI77K7"
	 "jTyVlFB7ECexrB9r3DmHZ1ljC6zNwqnrSBhzwvNEgsh9Jaf2ufWOTfKTE0w6GXJpj2ZF29IYy0Oo"
	 "fMfyk8r+TbXHtgt1XQ0jhPeE0STsTcEPw1CMpT/OGfeb/Fsou0fBOwc4nHdF1+7Xyw/yXYwBaHsO"
	 "RfiFeHKXRpgA4AdzSkCc7oWlvyOQsX32IlEJ74XHAAnHQZXZTkOiBtgIgcwCKWeAwvYj8It6GAYk"
	 "dYHhGQbn823hT3fzG5JKSVaFwXHwWcFi4N/gEmWgnpouD7JfU1CZ8fe0X1dOAbIm8XA7gw22YXu4"
	 "zSamzZPHg2VQq1DNgrucPU6V2zzWFMKCqpfk9E5D/yPPApTUAuZ4Odgy+52GQEwbBKoZzAn3Qoo6"
	 "bLJKB1hP+N+jMtyybeGPJSsCTLQyFZUNGclz8Oco3/bso3fmF88kZrOuN1N6ned3II1M//ctRm2a"
	 "dmGh6Xrnvm3Dg3esHmI6EU5bOlHV+y/yk6r8TVnEtvhhOrf4NZUtW2WYfzrQ7Sbml1XOsfiZPxv0"
	 "/Xe2+OCKxfQLOb2j46o81znNgyweF2IWyEpbFkjw9IwlMS/kRvtrm4nemPdtN95WJ1PyGhbZaDTD"
	 "em3By/uh3NbXd6v9OzMDcBTqIjD+5BzLTvzf7SRW9xlYtjKNTD9hMJ8yjmjWQODl6IYynveggHoX"
	 "N2I6ETc09iAodb1npdd7GTAK73NZ2DsYvQ/9GBMfWdYyb/Z7LQYVdc8hJbYfktpo9EPkk+l89Z0+"
	 "zbtXP80PKurJBfSsun0t6pcNJNipY9Yw+uAieRTo1jd8Q7ckH2Y9RdNuz8Xs6SDQobQ8A9rotE7C"
	 "CA7W11veuDc1fKpq1Xsd8XVZy57CPSxyTT/F6Xcy4nKBfwsjTDt71m/OQ3dM+1n3he3V/0Y2nD40"
	 "NhwobZ1npdd3GbgK71PdkkfpN8+IDcvIBw6aNYQ5I1UlwpfTQFrjQrKo8mUnbrpWdly/6Q6OSYzo"
	 "v9VPk2qPiMEz4v6Cwj8OfRF3YjrkFvhMupv2Na6T5K5syBJWIv8Z+o5lhEj2W5eSbuhMyFYQOjpl"
	 "dC3XTKDcRrqlaGld3AybAnATK+IYoy4G/HKh77jBA8uKD7CjBoQ4igAdaSbMRhJOUttweciz+LyC"
	 "mdGXHE26/xBWgtHGYAv9n/J1RfkTtyciZ5eAaAlBOZ8HJ8axZXwJdMI7nhD/k8mWC8HDkFsfCaQQ"
	 "6Xiw7sUtm7aF3PECXp8tVDUsXs1LV86D/Ga99XwV5PSBaIiNfEXbdJfFHbqLUmxA6tjXmfFNk9V3"
	 "8UlPyQntFtEoqgHFNgtIV/2Tq5wEHcMPlxPY40haDO0ssItig3lhOCBl"
	)
)




;;;函数名称:  Aisp-Load_ODCL_Project
;;;参数：projname = 工程名称字串(后缀为"*.odcl"、"*.odcl.lsp"或不带后缀)或者OpenDcl工程数据表
;;;      reload =  T 强制重载工程 or nil 若已加载，则什么也不干
;;;      password = 设定密码字串 or nil
;;;      alias = 替代项目关键字 or nil
;;;返回值:
;;;加载OpenDcl工程
(defun Aisp-Load_ODCL_Project
       (projname reload password alias / bytes rtype Projects e)
  (cond
    ((null dcl_project_import)
     (prompt "OpenDCL未加载...\n")
    )
    ((= 'list (type projname)) ;_ projname 为OpenDcl工程数据表
     (dcl_project_import projname password alias)
    )
    ((and
       (progn
	 (if (=	".LSP"
		(substr (strcase projname) (- (strlen projname) 3))
	     )
	   (setq projname (substr projname 1 (- (strlen projname) 4)))
	 )
	 (if (/= ".ODCL"
		 (substr (strcase projname) (- (strlen projname) 4))
	     )
	   (setq projname (strcat projname ".odcl"))
	 )
	 (setq bytes (vl-get-resource projname))
       )
       (eq 'str (setq rtype (type bytes)))
       (not (eq "" bytes))
     ) ;_ 从打包的资源文件中读取OpenDCL工程
     (if reload
       (dcl_project_import bytes password alias)
       (if (or
	     (not (setq Projects (dcl_GetProjects)))
	     (not (member (strcase (vl-filename-base projname))
			  (mapcar 'strcase Projects)
		  )
	     )
	   )
	 (dcl_project_import bytes password alias)
       )
     )
    )
    ;;查找OpenDCL工程文件进行加载
    ((if (not (VL-CATCH-ALL-ERROR-P
		(setq e	(VL-CATCH-ALL-APPLY
			  'dcl_project_load
			  (list (findfile projname) reload alias)
			)
		)
	      )
	 )
       e
     )
    )
  )
)

;;;函数名称: Aisp-AutoLoadODclArx
;;;参数: 无参数
;;;返回值: loaded
;;;自动加载OpenDcl函数
(defun Aisp-AutoLoadODclArx (/ loaded fn v fnn)
  ;;系统已安装OpenDcl的加载方式
  (if (and
	(not dcl_getversionex) ;_ OpenDcl未加载
	(= 2 (boole 1 (getvar "DEMANDLOAD") 2))
      )
    (VL-CATCH-ALL-APPLY 'vl-cmdf (list "opendcl")) ;_ 调用OpenDcl命令加载OpenDcl
  )
  (if (not dcl_getversionex) ;_ OpenDcl仍未加载
    ;;按AutoCAD的不同版本搜索opendcl.arx文件进行加载
    (cond
      ((= "16" (setq v (itoa (atoi (getvar 'acadver)))))
       (if
	 (setq fnn (findfile (setq fn (strcat "opendcl." v ".arx"))))
	  (setq loaded (arxload fnn "1"))
	  (setq loaded "2")
       )
      )
      ((or (= "17" v) (= "18" v) (= "19" v) (= "20" v))
       (if (= "x86" (getenv "PROCESSOR_ARCHITECTURE")) ;_ 32位系统
	 (if (setq fnn
		    (findfile (setq fn (strcat "opendcl." v ".arx")))
	     )
	   (setq loaded (arxload fnn "1"))
	   (setq loaded "2")
	 )
	 ;;64位系统
	 (if (setq fnn
		    (findfile (setq fn (strcat "opendcl.x64." v ".arx")))
	     )
	   (progn
	     (setq loaded
		  (arxload fnn
			   "1"
		  )
	   )
	     (setq loaded "3")
	   )
	   (setq loaded "2")
	 )
       )
      )
      (t (Setq loaded "2"))
    )
    (setq loaded "3") ;_ 已加载
  )
  ;; 加载OpenDcl失败，直接中断程序
  (if (= "1" loaded)
    (progn
      (princ (strcat fn "加载失败！程序将退出！"))
      (exit)
    )
    (if	(= "2" loaded)
      (progn
	(princ
	  (strcat "未找到对应的\"" fn "\"文件！程序将退出！")
	)
	(exit)
      )
    )
  )
  ;;返回3，表示加载成功
  loaded
)

;;;窗体加载
(if (= (Aisp-AutoLoadODclArx) "3")
  (progn
    (Aisp-Load_ODCL_Project INTERFACE T nil nil)
    (dcl-Form-Show Interface/MainFrame)
  )
)

;;;窗体关闭,重新加载窗体
(defun c:reload (/)
  (if (not (dcl-Form-IsActive Interface/MainFrame))
    (dcl-Form-Show Interface/MainFrame)
  )
  (princ)
)
